module ietf-yang-push-netobs-timestamping {
     yang-version 1.1;
     namespace
       "urn:ietf:params:xml:ns:yang:ietf-yang-push-netobs-timestamping";
     prefix ypnt;
     import ietf-yang-types {
       prefix yang;
       reference
         "RFC 6991: Common YANG Data Types";
     }
     import ietf-yang-push {
       prefix yp;
       reference
         "RFC 8641: Subscription to YANG Notifications for Datastore Updates";
     }
     organization "IETF NETCONF (Network Configuration) Working Group";
     contact
       "WG Web:   <http:/tools.ietf.org/wg/netconf/>
        WG List:  <mailto:netconf@ietf.org>

        Authors:  Thomas Graf
                  <mailto:thomas.graf@swisscom.com>
                  Benoit Claise
                  <mailto:benoit.claise@huawei.com>
                  Alex Huang Feng
                  <mailto:alex.huang-feng@insa-lyon.fr>";

     description
       "Defines YANG push event notification header with the observation
       time in push-update and push-change-update notifications.

       Copyright (c) 2023 IETF Trust and the persons identified as
       authors of the code.  All rights reserved.

       Redistribution and use in source and binary forms, with or without
       modification, is permitted pursuant to, and subject to the license
       terms contained in, the Revised BSD License set forth in Section
       4.c of the IETF Trust's Legal Provisions Relating to IETF Documents
       (https://trustee.ietf.org/license-info).

       This version of this YANG module is part of RFC XXXX; see the RFC
       itself for full legal notices.";

     revision 2023-03-06 {
       description
         "First revision";
       reference
         "RFC XXXX: Support of YANG Notifications Observation Time";
     }

     feature yang-push-change-update-obs-timestamp {
       description
         "This feature indicates the YANG-push Notifications support
         the observation timestamps in the push-change-update notifications.";
     }

     feature yang-push-update-obs-timestamp {
       description
         "This feature indicates the YANG-push Notifications support
         the observation timestamps in the push-update notifications.";
     }

     grouping yang-push-update-obs-timestamp {
       description
         "This grouping adds the start timestamp and the end timestamp of the
         observed metrics.";
       leaf observation-time {
         type yang:date-and-time;
         description
           "This is the time when metrics started counting.";
       }
     }

     grouping yang-push-change-update-obs-timestamp {
       description
         "This grouping adds the timestamp of the recorded event.";
       leaf state-changed-observation-time {
         type yang:date-and-time;
         description
           "This is the time when event happened.";
       }
     }

     // Event notifications
     augment "/yp:push-update" {
       description
         "This augmentation adds the start timestamp of the counted metrics
         in the push-update notification.";
       uses ypnt:yang-push-update-obs-timestamp;
     }

     augment "/yp:push-change-update" {
       description
         "This augmentation adds the timestamp of the event in the push-change-update
         notification.";
         uses ypnt:yang-push-change-update-obs-timestamp;
     }
   }
